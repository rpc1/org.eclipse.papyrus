# SysMLmodel
generated by Papyrus Requirement from exportSpecObject.uml

# Specification: SysMLmodel

## R1: Class (Stereotype5)
- Attribute1: Low
- Attribute2: Idea

## R2: Class_1 (Stereotype5)
- Attribute1: Medium
- Attribute2: Idea

## R3: Class_2 (Stereotype5)
- Attribute1: High
- Attribute2: Idea

## R4: Class_3 (Stereotype5)
- Attribute1: Medium
- Attribute2: Proto

## R5: Class_4 (Stereotype5)
- Attribute1: High
- Attribute2: Specification

## R6: Class1 (Stereotype1)
- Attribute1: test3

## R7: Class1_1 (Stereotype1)
- Attribute1: test1

## R8: Class1_2 (Stereotype1)
- Attribute1: test2

## R9: Class1_3 (Stereotype1)
- Attribute1: test4

## R10: Class1_4 (Stereotype1)
- Attribute1: test5

## R11: Class2 (Stereotype6)
- Attribute1: testXhtml
