# SysMLmodel
generated by Papyrus Requirement from exportSpecRealtions.uml

# Specification: SysMLmodel

## req100: CopyOf_Stereotype1_11 (CopyOf_Stereotype1_1)
- Stereotype1 -> req200
- Stereotype2 -> req400
- Stereotype3 -> req600
- Stereotype4 -> req500

### req110: CopyOf_Stereotype1_11 (CopyOf_Stereotype1_1)
- Stereotype2 -> req410

### req120: CopyOf_Stereotype4_11 (CopyOf_Stereotype4_1)
- Attribute1: 0.0

### req130: CopyOf_Stereotype5_11 (CopyOf_Stereotype5_1)
- Attribute1: Low
- Attribute2: Idea
- Stereotype3 -> req140

### req140: CopyOf_Stereotype5_12 (CopyOf_Stereotype5_1)
- Attribute1: Low
- Attribute2: Idea

### req150: CopyOf_Stereotype5_13 (CopyOf_Stereotype5_1)
- Attribute1: Low
- Attribute2: Idea
- Stereotype5 -> req120

### req160: CopyOf_Stereotype5_14 (CopyOf_Stereotype5_1)
- Attribute1: Low
- Attribute2: Idea
- Stereotype4 -> req120

## req200: CopyOf_Stereotype2_11 (CopyOf_Stereotype2_1)
- Attribute1: 0

### req210: CopyOf_Stereotype1_11 (CopyOf_Stereotype1_1)

## req300: CopyOf_Stereotype3_11 (CopyOf_Stereotype3_1)
- Attribute1: false

### req310: CopyOf_Stereotype2_11 (CopyOf_Stereotype2_1)
- Attribute1: 0

## req400: CopyOf_Stereotype3_12 (CopyOf_Stereotype3_1)
- Attribute1: false

### req410: CopyOf_Stereotype1_11 (CopyOf_Stereotype1_1)

## req500: CopyOf_Stereotype4_11 (CopyOf_Stereotype4_1)
- Attribute1: 0.0

## req600: CopyOf_Stereotype5_11 (CopyOf_Stereotype5_1)
- Attribute1: Low
- Attribute2: Idea
