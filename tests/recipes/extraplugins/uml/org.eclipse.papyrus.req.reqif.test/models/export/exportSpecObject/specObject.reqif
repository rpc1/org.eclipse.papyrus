# SysMLmodel
generated by Papyrus Requirement from exportSpecObject.uml

# Specification: SysMLmodel

## 1: Class (Stereotype5)
- Attribute1: Low
- Attribute2: Idea

## 2: Class_1 (Stereotype5)
- Attribute1: Medium
- Attribute2: Idea

## 3: Class_2 (Stereotype5)
- Attribute1: High
- Attribute2: Idea

## 4: Class_3 (Stereotype5)
- Attribute1: Medium
- Attribute2: Proto

## 5: Class_4 (Stereotype5)
- Attribute1: High
- Attribute2: Specification

## 6: Class1 (Stereotype1)
- Attribute1: test3

## 7: Class1_1 (Stereotype1)
- Attribute1: test1

## 8: Class1_2 (Stereotype1)
- Attribute1: test2

## 9: Class1_3 (Stereotype1)
- Attribute1: test4

## 10: Class1_4 (Stereotype1)
- Attribute1: test5
