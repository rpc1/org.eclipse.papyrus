# SysMLmodel
generated by Papyrus Requirement from exportSpecObject.uml

# Specification: SysMLmodel

## 1: Req_0 (ReqType5)
- Attribute1: Low
- Attribute2: Idea

## 2: Req_1 (ReqType5)
- Attribute1: Medium
- Attribute2: Idea

## 3: Req_2 (ReqType5)
- Attribute1: High
- Attribute2: Idea

## 4: Req_3 (ReqType5)
- Attribute1: Medium
- Attribute2: Proto

## 5: Req_4 (ReqType5)
- Attribute1: High
- Attribute2: Specification

## 6: Req_5 (ReqType1)
- Attribute1: test3

## 7: Req_6 (ReqType1)
- Attribute1: test1

## 8: Req_7 (ReqType1)
- Attribute1: test2

## 9: Req_8 (ReqType1)
- Attribute1: test4

## 10: Req_9 (ReqType1)
- Attribute1: test5
