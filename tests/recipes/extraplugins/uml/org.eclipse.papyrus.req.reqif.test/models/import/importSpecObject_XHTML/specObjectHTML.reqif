# SysMLmodel
generated by Papyrus Requirement from exportSpecObject.uml

# Specification: SysMLmodel

## R1: Req_0 (ReqType5)
- Attribute1: Low
- Attribute2: Idea

## R2: Req_1 (ReqType5)
- Attribute1: Medium
- Attribute2: Idea

## R3: Req_2 (ReqType5)
- Attribute1: High
- Attribute2: Idea

## R4: Req_3 (ReqType5)
- Attribute1: Medium
- Attribute2: Proto

## R5: Req_4 (ReqType5)
- Attribute1: High
- Attribute2: Specification

## R6: Req_5 (ReqType1)
- Attribute1: test3

## R7: Req_6 (ReqType1)
- Attribute1: test1

## R8: Req_7 (ReqType1)
- Attribute1: test2

## R9: Req_8 (ReqType1)
- Attribute1: test4

## R10: Req_9 (ReqType1)
- Attribute1: test5

## R11: Req_10 (ReqType6)
- Attribute1: testXhtml
