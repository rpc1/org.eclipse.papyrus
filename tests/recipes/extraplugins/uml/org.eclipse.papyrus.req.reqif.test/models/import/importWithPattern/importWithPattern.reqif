# SysMLmodel
generated by Papyrus Requirement from exportSpecObject.uml

# Specification: specif

## 1: Req_0
aaaaaaa
- Attribute1: Low
- Attribute2: Idea

## 2: Req_2
bbbbbbbb
- Attribute1: Medium
- Attribute2: Idea

## 3: Req_3
cccccccccc
- Attribute1: High
- Attribute2: Idea

## 4: Req_4
ddddddddddd
- Attribute1: Medium
- Attribute2: Proto

## 5: Req_5
eeeeeeeeeeeeee
- Attribute1: High
- Attribute2: Specification
